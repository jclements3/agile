// generated by reqif2sysml.pl from tidewater.reqif -- review before committing
package 'Stakeholder Needs' {
    requirement TW_STK_001 { doc /* The network shall provide marine weather observations for the coastal region it covers. */ attribute doorsId = "TW-STK-001"; attribute title = "Coastal coverage"; }
    requirement TW_STK_002 { doc /* Forecasters shall receive observations in time to use them in the next bulletin. */ attribute doorsId = "TW-STK-002"; attribute title = "Timely observations"; }
    requirement TW_STK_003 { doc /* Mariners shall be able to read the latest bulletin and observations from a public service. */ attribute doorsId = "TW-STK-003"; attribute title = "Public access"; }
    requirement TW_STK_004 { doc /* Field crews shall be able to service any station from a single service vessel. */ attribute doorsId = "TW-STK-004"; attribute title = "Serviceable in the field"; }
    requirement TW_STK_005 { doc /* Past observations shall be kept so earlier conditions can be reviewed. */ attribute doorsId = "TW-STK-005"; attribute title = "Observation history"; }
    requirement TW_STK_006 { doc /* Offshore stations shall keep observing without shore power. */ attribute doorsId = "TW-STK-006"; attribute title = "Off-grid operation"; }
}
