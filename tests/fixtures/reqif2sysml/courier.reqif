# Courier system requirements

# Specification: System Requirements

## 1: Mission

### 101: Endurance
The drone shall fly 30 min with a 2 kg parcel
at 15 m/s & 20°C.
- Verification Method: Test
- Priority: 1
- Margin: 0.15
- Last Reviewed: 2026-09-15T00:00:00Z

### 102
The drone shall carry:
- a 2 kg parcel, or
- two 1 kg parcels.
- Verification Method: Test, Analysis

## 2: Safety & Environment

### 3: Noise

#### 103
| Phase | Limit |
| --- | --- |
| Hover | 70 dBA |
Measured at 10 m. Do not use <raw> markup.
- satisfies -> 2

#### 104

## 4: Reserved

# Specification: Battery Requirements

## 210
Use 6S Li-ion cells.
- Verification Method: Inspection
- derived from -> 101

### 211
Charge to 80 % in 45 min.
- DOORS link -> 102

## 999
A deleted-but-exported object.
