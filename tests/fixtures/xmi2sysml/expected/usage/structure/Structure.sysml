// generated by xmi2sysml.pl from courier.xmi -- review before committing; TODO lines need a person
package Structure {
    private import Structure::Types::*;
    doc /* Physical architecture of the Courier drone & its power chain. */
    part def Drone {
        doc
            /*
             * A parcel-carrying multirotor.
             * Flies at most 40 °C ambient.
             */
        part airframe : Airframe;
        part battery : Battery[1..2];
        part fc : FlightController;
        part motors : Motor[4];
        ref part operator : Operator;
        attribute mass : Mass = 1.5;
        attribute mode : FlightMode = FlightMode::cruise;
        attribute 'serial number' : ScalarValues::String;
        connection power connect battery.pwrOut to fc.pwrIn;
        connection connect fc.rpmOut to motors.rpmCmd;
        bind mass = airframe.mass;
        // TODO uml:Operation 'arm' (xmi:id _op_arm): no SysML v2 mapping in this converter
        // TODO uml:Constraint 'massLimit' (xmi:id _rule_mass): constraint: OCL: self.mass <= 2.5
    }
    part def QuadDrone :> Drone;
    part def Airframe {
        attribute mass : Mass;
    }
    part def Battery {
        // TODO stereotype Safety:Hazardous on this element (xmi:id _s26) not converted
        port pwrOut : PowerIF;
        attribute 'nominal voltage' : Voltage;
    }
    part def FlightController {
        port pwrIn : ~PowerIF;
        port rpmOut { out attribute flowValue : ScalarValues::Real; }
        // TODO uml:StateMachine 'FlightModes' (xmi:id _sm_fc): no SysML v2 mapping in this converter
    }
    part def Motor {
        port rpmCmd { in attribute flowValue : ScalarValues::Real; }
    }
    part def Operator;
    port def PowerIF {
        out attribute current : Current;
        in item command : Command;
    }
    item def Command {
        attribute code : ScalarValues::Integer;
    }
    package Types {
        attribute def Mass :> ScalarValues::Real {
            // SysML 1.x unit: kilogram -- specialize an ISQ quantity value by hand
        }
        attribute def Voltage :> ScalarValues::Real;
        attribute def Current;
        // TODO uml:InstanceSpecification 'kilogram' (xmi:id _unit_kg): no SysML v2 mapping in this converter
        enum def FlightMode {
            enum hover;
            enum cruise;
            enum 'return';
        }
    }
}
