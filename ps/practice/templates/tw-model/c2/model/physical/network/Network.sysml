// generated by xmi2sysml.pl from tidewater.xmi -- review before committing; TODO lines need a person
package Network {
    private import DataCenter::*;
    private import Operations::*;
    private import Stations::*;
    doc /* The observation network as a whole, its users and what they do with it. */
    part def ObservationNetwork {
        // TODO stereotype Tidewater_Profile:L1Network on this element (xmi:id _22_1_7f3a0c1_70e9bef7d9f2) not converted
        doc /* Every station, the data center and the field crew that keeps them running. */
        part stations : StationSegment;
        part dataCenter : DataSegment;
        part operations : OperationsSegment;
        connection observationLink connect stations.obsOut to dataCenter.obsIn;
        connection healthLink connect stations.healthOut to dataCenter.healthIn;
    }
    part def NetworkContext {
        doc /* The network among the people who use and service it. */
        part network : ObservationNetwork;
        ref part forecaster : Forecaster;
        ref part mariner : Mariner;
        ref part technician : Technician;
        // TODO uml:Interaction 'DailyUpload' (xmi:id _22_1_7f3a0c1_db6d13407a41): no SysML v2 mapping in this converter
    }
    part def Forecaster {
        doc /* Writes forecasts from the observations. */
    }
    part def Mariner {
        doc /* Reads the bulletin before going out. */
    }
    part def Technician {
        doc /* Services stations from the vessel. */
    }
    use case def ReadBulletin {
        doc /* A mariner reads the latest bulletin. */
    }
    use case def ReviewObservations {
        doc /* A forecaster reviews recent and past observations. */
        // TODO uml:Include (xmi:id _22_1_7f3a0c1_08793d6918c3): no SysML v2 mapping in this converter
    }
    use case def QueryArchive {
        doc /* Look up observations by station and time. */
    }
    use case def ServiceStation {
        doc /* A technician visits, inspects and repairs a station. */
    }
    dependency from ObservationNetwork to MaintenanceDepot; // dependency
}
