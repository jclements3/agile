package HalberdNeeds {
    doc /* Stakeholder needs. */
    requirement <'N-001'> defendAsset { doc /* Defend the designated asset against the threat set. */ }
    requirement <'N-002'> operateOnRange { doc /* Be testable on the existing range. */ }
}
