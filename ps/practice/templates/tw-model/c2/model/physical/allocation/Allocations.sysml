// generated by xmi2sysml.pl from tidewater.xmi -- review before committing; TODO lines need a person
package Allocations {
    private import Behavior::*;
    private import DataCenter::*;
    private import Stations::*;
    doc /* Which part performs which step of the observation cycle. */
    allocate SampleSensors to SensorSuite;
    allocate TransmitObservations to TelemetryUnit;
    allocate IngestObservations to IngestService;
    allocate CheckQuality to QualityControl;
    allocate ArchiveObservations to Archive;
    allocate PublishBulletin to BulletinPublisher;
    allocate ReportHealth to ObservingStation;
}
