// generated by xmi2sysml.pl from tidewater.xmi -- review before committing; TODO lines need a person
package Operations {
    private import Network::*;
    doc /* The field crew and what it needs to keep the stations running. */
    part def OperationsSegment {
        // TODO stereotype Tidewater_Profile:L2Segment on this element (xmi:id _22_1_7f3a0c1_2706fb7aeda5) not converted
        doc /* The depot, the vessel and the spares. */
        part depot : MaintenanceDepot;
        part vessel : ServiceVessel;
        part spares : SparesPool;
    }
    part def MaintenanceDepot {
        // TODO stereotype Tidewater_Profile:L3Station on this element (xmi:id _22_1_7f3a0c1_b1d4c078ed7c) not converted
        doc /* Where stations are refurbished. */
    }
    part def ServiceVessel {
        // TODO stereotype Tidewater_Profile:L3Station on this element (xmi:id _22_1_7f3a0c1_50595ad943f8) not converted
        doc /* Carries the crew and a spare buoy. */
        part crane : DeckCrane;
    }
    part def DeckCrane {
        // TODO stereotype Tidewater_Profile:L4Subsystem on this element (xmi:id _22_1_7f3a0c1_6395cad437db) not converted
        doc /* Lifts a buoy aboard. */
    }
    part def SparesPool {
        // TODO stereotype Tidewater_Profile:L3Station on this element (xmi:id _22_1_7f3a0c1_956bd848fcb7) not converted
        doc /* Spare sensors, batteries and one spare buoy. */
    }
    dependency from ServiceVessel to Technician; // dependency
}
