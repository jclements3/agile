// generated by reqif2sysml.pl from courier.reqif -- review before committing
package 'System Requirements unplaced' {
    requirement CD_999 { doc /* A deleted-but-exported object. */ attribute doorsId = "CD-999"; }
}
