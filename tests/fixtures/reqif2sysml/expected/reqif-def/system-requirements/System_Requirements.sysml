// generated by reqif2sysml.pl from courier.reqif -- review before committing
package 'System Requirements' {
    package Mission {
        // DOORS heading CD-1
        requirement def CD_101 {
            doc
                /*
                 * The drone shall fly 30 min with a 2 kg parcel
                 * at 15 m/s & 20°C.
                 */
            attribute doorsId = "CD-101";
            attribute title = "Endurance";
            attribute verificationMethod = "Test";
        }
        requirement def CD_102 {
            doc
                /*
                 * The drone shall carry:
                 * - a 2 kg parcel, or
                 * - two 1 kg parcels.
                 */
            attribute doorsId = "CD-102";
            attribute verificationMethod = "Test, Analysis";
        }
    }
    package 'Safety & Environment' {
        // DOORS heading CD-2
        package Noise {
            // DOORS heading CD-3
            requirement def CD_103 {
                doc
                    /*
                     * Phase | Limit
                     * Hover | 70 dBA
                     * Measured at 10 m. Do not use <raw> markup.
                     */
                attribute doorsId = "CD-103";
            }
            // TODO DOORS object CD-104 has neither text nor heading
        }
    }
    package Reserved {
        // DOORS heading CD-4
    }
    // links (DOORS link modules)
    // TODO link rel-3 (satisfies): CD-103 -> CD-2 is not between two requirements
}
