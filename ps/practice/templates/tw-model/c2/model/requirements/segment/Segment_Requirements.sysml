// generated by reqif2sysml.pl from tidewater.reqif -- review before committing
package 'Segment Requirements' {
    private import 'Segment Requirements'::'Data Center'::*;
    private import 'Segment Requirements'::Stations::*;
    private import 'System Requirements'::Functions::*;
    private import 'System Requirements'::Operations::*;
    private import RequirementDerivation::*;
    package Stations {
        // DOORS heading 30
        requirement TW_SEG_001 { doc /* The buoy hull shall carry the sensor suite above the waterline. */ attribute doorsId = "TW-SEG-001"; attribute title = "Sensor height"; attribute verificationMethod = "Inspection"; }
        requirement TW_SEG_002 { doc /* The mooring shall keep the buoy within its assigned watch circle. */ attribute doorsId = "TW-SEG-002"; attribute title = "Watch circle"; attribute verificationMethod = "Analysis"; }
        requirement TW_SEG_003 { doc /* The power system shall report the battery state of charge. */ attribute doorsId = "TW-SEG-003"; attribute title = "State of charge"; attribute verificationMethod = "Test"; }
        requirement TW_SEG_004 { doc /* The telemetry unit shall retry a failed transmission. */ attribute doorsId = "TW-SEG-004"; attribute title = "Retry"; attribute verificationMethod = "Test"; }
    }
    package 'Data Center' {
        // DOORS heading 35
        requirement TW_SEG_005 { doc /* The ingest service shall discard duplicate observations. */ attribute doorsId = "TW-SEG-005"; attribute title = "Duplicates"; attribute verificationMethod = "Test"; }
        requirement TW_SEG_006 { doc /* The quality control service shall record why an observation was flagged. */ attribute doorsId = "TW-SEG-006"; attribute title = "Flag reason"; attribute verificationMethod = "Test"; }
        requirement TW_SEG_007 { doc /* The archive shall return any observation by station and time. */ attribute doorsId = "TW-SEG-007"; attribute title = "Retrieval"; attribute verificationMethod = "Demonstration"; }
        requirement TW_SEG_008 { doc /* The publisher shall stamp each bulletin with its issue time. */ attribute doorsId = "TW-SEG-008"; attribute title = "Issue time"; attribute verificationMethod = "Inspection"; }
    }
    // links (DOORS link modules)
    #derivation connection {
        end #original ::> TW_SYS_001;
        end #derive ::> TW_SEG_001;
    }
    #derivation connection {
        end #original ::> TW_SYS_001;
        end #derive ::> TW_SEG_002;
    }
    #derivation connection {
        end #original ::> TW_SYS_011;
        end #derive ::> TW_SEG_003;
    }
    #derivation connection {
        end #original ::> TW_SYS_013;
        end #derive ::> TW_SEG_004;
    }
    #derivation connection {
        end #original ::> TW_SYS_003;
        end #derive ::> TW_SEG_005;
    }
    #derivation connection {
        end #original ::> TW_SYS_004;
        end #derive ::> TW_SEG_006;
    }
    #derivation connection {
        end #original ::> TW_SYS_005;
        end #derive ::> TW_SEG_007;
    }
    #derivation connection {
        end #original ::> TW_SYS_006;
        end #derive ::> TW_SEG_008;
    }
}
