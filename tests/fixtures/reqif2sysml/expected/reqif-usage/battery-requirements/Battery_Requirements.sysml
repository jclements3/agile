// generated by reqif2sysml.pl from courier.reqif -- review before committing
package 'Battery Requirements' {
    private import 'System Requirements'::Mission::*;
    private import RequirementDerivation::*;
    requirement CD_210 { doc /* Use 6S Li-ion cells. */ attribute doorsId = "CD-210"; attribute verificationMethod = "Inspection"; }
    requirement CD_211 { doc /* Charge to 80 % in 45 min. */ attribute doorsId = "CD-211"; }
    // links (DOORS link modules)
    #derivation connection {
        end #original ::> CD_101;
        end #derive ::> CD_210;
    }
    dependency from CD_211 to CD_102; // trace (DOORS link)
}
