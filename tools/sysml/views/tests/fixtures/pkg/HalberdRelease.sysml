package HalberdRelease {
    doc /* U release package. The ReplayThreat is mentioned here only in a comment. */
    private import SecMeta::*;
    public import HalberdFireControl::*;   // re-exports CUI content into a U package
    @Marking { level = Level::U; }
    // TODO: JammerModel summary goes here
}
