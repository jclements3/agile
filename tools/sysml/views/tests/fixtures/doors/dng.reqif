# Specification: Stakeholder Needs

## STK-1: Mission needs (Heading)

### STK-3: Defend the asset (Stakeholder Requirement)
The system shall defend the designated asset against the threat set.
- Priority: High

### o-4 (Information)
Threat set is defined in the STAR.
