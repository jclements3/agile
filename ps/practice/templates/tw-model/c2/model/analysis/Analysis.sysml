// generated by xmi2sysml.pl from tidewater.xmi -- review before committing; TODO lines need a person
package Analysis {
    private import Types::*;
    doc /* Constraint blocks used in parametric diagrams. */
    constraint def EnergyBalance {
        doc /* Daily energy in must cover daily energy out, with the battery as the buffer. */
        // TODO constraint expression (parametrics) not converted
        attribute generation : Power;
        attribute storage : Energy;
        attribute load : Power;
        // TODO uml:Constraint 'balance' (xmi:id _22_1_7f3a0c1_f2cac788664a): constraint: English: generation * sunHours >= load * 24
    }
}
