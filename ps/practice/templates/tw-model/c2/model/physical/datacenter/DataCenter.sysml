// generated by xmi2sysml.pl from tidewater.xmi -- review before committing; TODO lines need a person
package DataCenter {
    private import Interfaces::*;
    private import Stations::*;
    doc /* The services that turn observations into an archive and a bulletin. */
    part def DataSegment {
        // TODO stereotype Tidewater_Profile:L2Segment on this element (xmi:id _22_1_7f3a0c1_85cf3a7fcfb9) not converted
        doc /* Ingest, quality control, archive and publication. */
        part ingest : IngestService;
        part qc : QualityControl;
        part archive : Archive;
        part publisher : BulletinPublisher;
        port obsIn : ~ObservationIF;
        port healthIn : ~HealthIF;
        port publicOut : PublicIF;
        connection connect obsIn to ingest.obsIn;
        connection toQc connect ingest.'out' to qc.'in';
        connection toArchive connect qc.'out' to archive.'in';
        connection toPublisher connect archive.query to publisher.source;
        connection connect publisher.publicOut to publicOut;
    }
    part def IngestService {
        // TODO stereotype Tidewater_Profile:L3Station on this element (xmi:id _22_1_7f3a0c1_512bca4a299e) not converted
        doc /* Receives and de-duplicates observations. */
        port obsIn : ~ObservationIF;
        port 'out' : ObservationIF;
    }
    part def QualityControl {
        // TODO stereotype Tidewater_Profile:L3Station on this element (xmi:id _22_1_7f3a0c1_2027db3db6d9) not converted
        doc /* Checks each observation and sets its flag. */
        doc
            /*
             * From the Ops Concept briefing, slide 22: QC flags are reviewed by the duty forecaster each morning. Para 4.1.2 of the CONOPS applies.
             */
        port 'in' : ~ObservationIF;
        port 'out' : ObservationIF;
    }
    dependency from QualityControl to SensorSuite; // dependency
    part def Archive {
        // TODO stereotype Tidewater_Profile:L3Station on this element (xmi:id _22_1_7f3a0c1_6e5790fc7a9c) not converted
        doc /* Keeps every observation with its flag. */
        port 'in' : ~ObservationIF;
        port query : ObservationIF;
    }
    part def BulletinPublisher {
        // TODO stereotype Tidewater_Profile:L3Station on this element (xmi:id _22_1_7f3a0c1_aa13c1bc4e5f) not converted
        doc /* Writes and publishes the marine bulletin. */
        port source : ~ObservationIF;
        port publicOut : PublicIF;
    }
}
