// generated by xmi2sysml.pl from courier.xmi -- review before committing; TODO lines need a person
package Requirements {
    private import Behavior::*;
    private import RequirementDerivation::*;
    private import Structure::*;
    requirement def CD_101 {
        doc
            /*
             * The drone shall fly 30 min with a 2 kg parcel
             * at 15 m/s.
             */
        attribute doorsId = "CD-101";
        attribute title = "Endurance";
    }
    requirement def CD_101_1 {
        doc /* Land with 10 % charge left. */
        attribute doorsId = "CD-101.1";
        attribute title = "Reserve";
    }
    requirement def CD_102 {
        doc /* Carry a payload of 2 kg. */
        attribute doorsId = "CD-102";
        attribute title = "Payload";
        attribute verificationMethod = "Test";
        attribute risk = "High";
    }
    requirement def CD_210 {
        doc /* Use 6S Li-ion cells. */
        attribute doorsId = "CD-210";
        attribute title = "Battery cells";
    }
    satisfy CD_101 by Drone;
    satisfy CD_102 by Drone::airframe;
    #derivation connection {
        end #original ::> CD_101;
        end #derive ::> CD_210;
    }
    dependency from Battery to CD_210; // trace
    allocate DeliverParcel to Drone;
}
