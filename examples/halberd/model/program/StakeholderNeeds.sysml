// Segment G (Government Program Office): the stakeholder needs, from the capability requirements.
package StakeholderNeeds {
    doc /* What the users and the program office need from Halberd, in their words. */
    private import SecMeta::*;
    @Marking { level = Level::U; }
    requirement stk01 { attribute doorsId = "HAL-STK-001"; doc /* Halberd shall defend an assigned area against a ballistic threat. */ }
    requirement stk02 { attribute doorsId = "HAL-STK-002"; doc /* Halberd shall take direction from, and report to, higher echelon command. */ }
    requirement stk03 { attribute doorsId = "HAL-STK-003"; doc /* Halberd shall share its air picture with adjacent defense units. */ }
    requirement stk04 { attribute doorsId = "HAL-STK-004"; doc /* Every engagement decision shall stay under positive human control. */ }
    requirement stk05 { attribute doorsId = "HAL-STK-005"; doc /* The fielding unit shall be able to transport and emplace Halberd itself. */ }
    requirement stk06 { attribute doorsId = "HAL-STK-006"; doc /* Halberd shall be sustainable by organic maintainers with depot support. */ }
    requirement stk07 { attribute doorsId = "HAL-STK-007"; doc /* Mission data and control paths shall be protected from cyber attack. */ }
    requirement stk08 { attribute doorsId = "HAL-STK-008"; doc /* Crews shall be able to train without expending live rounds. */ }
}
