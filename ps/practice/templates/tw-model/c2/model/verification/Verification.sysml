// generated by xmi2sysml.pl from tidewater.xmi -- review before committing; TODO lines need a person
package Verification {
    private import Requirements::'Segment Requirements'::'Data Center'::*;
    private import Requirements::'Segment Requirements'::Stations::*;
    private import Requirements::'System Requirements'::Functions::*;
    private import Requirements::'System Requirements'::Interfaces::*;
    private import Requirements::'System Requirements'::Operations::*;
    doc /* Test cases and what they verify. */
    verification def TestStationObservations {
        doc /* Sensors and transmission on a buoy and a shore station. */
        objective {
            verify TW_SYS_001;
            verify TW_SYS_002;
            verify TW_SYS_008;
            verify TW_SEG_001;
        }
    }
    verification def TestDataFlow {
        doc /* Ingest, quality control and archive with seeded bad records. */
        objective {
            verify TW_SYS_003;
            verify TW_SYS_004;
            verify TW_SYS_005;
            verify TW_SEG_005;
            verify TW_SEG_006;
            verify TW_SEG_007;
        }
    }
    verification def DemonstratePublication {
        doc /* A full bulletin cycle on the public service. */
        objective {
            verify TW_SYS_006;
            verify TW_SYS_007;
            verify TW_SYS_010;
            verify TW_SYS_015;
            verify TW_SEG_008;
        }
    }
    verification def InspectVesselAccess {
        doc /* Crew inspection of each station type from the vessel. */
        objective {
            verify TW_SYS_012;
        }
    }
    verification def TestHealthReporting {
        doc /* Health reports and mode changes, with a drained battery. */
        objective {
            verify TW_SYS_009;
            verify TW_SYS_014;
            verify TW_SEG_003;
        }
    }
    verification def TestStoreAndForward {
        doc /* Link outage and recovery. */
        objective {
            verify TW_SYS_013;
            verify TW_SEG_004;
        }
    }
}
