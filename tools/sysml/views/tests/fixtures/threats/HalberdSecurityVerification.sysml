package HalberdSecurityVerification {
    private import HalberdSecurityRequirements::*;
    verification def FrameAuthenticationTest {
        objective { verify frameAuthentication; }
    }
    // commandFreshness has no verification yet
}
