// generated by xmi2sysml.pl from tidewater.xmi -- review before committing; TODO lines need a person
package Tidewater {
    // TODO uml:Profile 'Tidewater Profile' (xmi:id _22_1_7f3a0c1_7d97481b1fe6): no SysML v2 mapping in this converter
}
