// generated by reqif2sysml.pl from courier.csv -- review before committing
package courier {
    package Mission {
        // DOORS heading CD-1
        requirement def CD_101 {
            doc
                /*
                 * The drone shall fly 30 min with a 2 kg parcel
                 * at 15 m/s.
                 */
            attribute doorsId = "CD-101";
            attribute verificationMethod = "Test";
        }
        requirement def CD_102 {
            doc /* Carry a "standard" 2 kg parcel. */
            attribute doorsId = "CD-102";
        }
    }
    package Safety {
        // DOORS heading CD-2
        package Noise {
            // DOORS heading CD-3
            requirement def CD_103 {
                doc /* Hover noise at most 70 dBA at 10 m. */
                attribute doorsId = "CD-103";
                attribute verificationMethod = "Analysis";
            }
        }
    }
    package Reserved {
        // DOORS heading CD-4
    }
}
