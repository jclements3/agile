// generated by xmi2sysml.pl from courier.xmi -- review before committing; TODO lines need a person
package Behavior {
    private import Requirements::*;
    action def DeliverParcel {
        in destination : ScalarValues::String;
        out delivered : ScalarValues::Boolean;
        action 'take off' : TakeOff;
        action drop;
        // TODO uml:DecisionNode 'landed?' (xmi:id _n_dec): activity node not converted
        first start then 'take off';
        first 'take off' then drop;
        // TODO uml:ControlFlow (xmi:id _e3): activity edge not converted (object flow, or an end that is a decision/fork/pin)
        first drop then done;
    }
    action def TakeOff;
    verification def EnduranceTest {
        objective {
            verify CD_101;
            verify CD_101_1;
        }
    }
}
