// generated by reqif2sysml.pl from tidewater.reqif -- review before committing
package 'System Requirements' {
    private import 'Stakeholder Needs'::*;
    private import 'System Requirements'::Functions::*;
    private import 'System Requirements'::Interfaces::*;
    private import 'System Requirements'::Operations::*;
    private import RequirementDerivation::*;
    package Functions {
        // DOORS heading 14
        requirement TW_SYS_001 { doc /* Each station shall measure wind, air pressure and air temperature, and each buoy shall also measure waves. */ attribute doorsId = "TW-SYS-001"; attribute title = "Measure conditions"; attribute verificationMethod = "Test"; }
        requirement TW_SYS_002 { doc /* Each station shall transmit its observations to the data center on a fixed schedule. */ attribute doorsId = "TW-SYS-002"; attribute title = "Scheduled transmission"; attribute verificationMethod = "Test"; }
        requirement TW_SYS_003 { doc /* The data center shall ingest every observation it receives. */ attribute doorsId = "TW-SYS-003"; attribute title = "Ingest"; attribute verificationMethod = "Test"; }
        requirement TW_SYS_004 { doc /* The data center shall flag observations that fail a quality check. */ attribute doorsId = "TW-SYS-004"; attribute title = "Quality control"; attribute verificationMethod = "Test"; }
        requirement TW_SYS_005 { doc /* The data center shall archive every observation together with its quality flag. */ attribute doorsId = "TW-SYS-005"; attribute title = "Archive"; attribute verificationMethod = "Demonstration"; }
        requirement TW_SYS_006 { doc /* The data center shall publish a marine bulletin twice a day, on a fixed schedule. */ attribute doorsId = "TW-SYS-006"; attribute title = "Bulletin"; attribute verificationMethod = "Demonstration"; }
        requirement TW_SYS_007 { doc /* The public service shall show the latest observation from every station. */ attribute doorsId = "TW-SYS-007"; attribute title = "Latest observations"; attribute verificationMethod = "Demonstration"; }
    }
    package Interfaces {
        // DOORS heading 18
        requirement TW_SYS_008 { doc /* Stations shall send observations to the data center over the observation interface. */ attribute doorsId = "TW-SYS-008"; attribute title = "Observation interface"; attribute verificationMethod = "Test"; }
        requirement TW_SYS_009 { doc /* Stations shall report their health to the data center over the health interface. */ attribute doorsId = "TW-SYS-009"; attribute title = "Health reporting"; attribute verificationMethod = "Test"; }
        requirement TW_SYS_010 { doc /* The data center shall offer observations through a documented public interface. */ attribute doorsId = "TW-SYS-010"; attribute title = "Public interface"; attribute verificationMethod = "Inspection"; }
    }
    package Operations {
        // DOORS heading 25
        requirement TW_SYS_011 { doc /* Each buoy shall run from its own solar panel and battery. */ attribute doorsId = "TW-SYS-011"; attribute title = "Own power"; attribute verificationMethod = "Analysis"; }
        requirement TW_SYS_012 { doc /* Every station shall be serviceable from the service vessel. */ attribute doorsId = "TW-SYS-012"; attribute title = "Vessel access"; attribute verificationMethod = "Inspection"; }
        requirement TW_SYS_013 { doc /* Each station shall keep observations it could not send and send them once the link returns. */ attribute doorsId = "TW-SYS-013"; attribute title = "Store and forward"; attribute verificationMethod = "Test"; }
        requirement TW_SYS_014 { doc /* Each station shall report its operating mode. */ attribute doorsId = "TW-SYS-014"; attribute title = "Operating mode"; attribute verificationMethod = "Test"; }
        requirement TW_SYS_015 { doc /* The data center shall keep a log of every bulletin it published. */ attribute doorsId = "TW-SYS-015"; attribute title = "Bulletin log"; attribute verificationMethod = "Inspection"; }
        requirement TW_SYS_016 { doc /* All stations and the data center shall use a common time reference. */ attribute doorsId = "TW-SYS-016"; attribute title = "Common time"; attribute verificationMethod = "Test"; }
    }
    // links (DOORS link modules)
    #derivation connection {
        end #original ::> TW_STK_001;
        end #derive ::> TW_SYS_001;
    }
    #derivation connection {
        end #original ::> TW_STK_002;
        end #derive ::> TW_SYS_002;
    }
    #derivation connection {
        end #original ::> TW_STK_002;
        end #derive ::> TW_SYS_003;
    }
    #derivation connection {
        end #original ::> TW_STK_002;
        end #derive ::> TW_SYS_004;
    }
    #derivation connection {
        end #original ::> TW_STK_005;
        end #derive ::> TW_SYS_005;
    }
    #derivation connection {
        end #original ::> TW_STK_003;
        end #derive ::> TW_SYS_006;
    }
    #derivation connection {
        end #original ::> TW_STK_003;
        end #derive ::> TW_SYS_007;
    }
    #derivation connection {
        end #original ::> TW_STK_002;
        end #derive ::> TW_SYS_008;
    }
    #derivation connection {
        end #original ::> TW_STK_004;
        end #derive ::> TW_SYS_009;
    }
    #derivation connection {
        end #original ::> TW_STK_003;
        end #derive ::> TW_SYS_010;
    }
    #derivation connection {
        end #original ::> TW_STK_006;
        end #derive ::> TW_SYS_011;
    }
    #derivation connection {
        end #original ::> TW_STK_004;
        end #derive ::> TW_SYS_012;
    }
    #derivation connection {
        end #original ::> TW_STK_002;
        end #derive ::> TW_SYS_013;
    }
    #derivation connection {
        end #original ::> TW_STK_004;
        end #derive ::> TW_SYS_014;
    }
    #derivation connection {
        end #original ::> TW_STK_005;
        end #derive ::> TW_SYS_015;
    }
    #derivation connection {
        end #original ::> TW_STK_002;
        end #derive ::> TW_SYS_016;
    }
}
