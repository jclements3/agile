// generated by xmi2sysml.pl from tidewater.xmi -- review before committing; TODO lines need a person
package Requirements {
    private import DataCenter::*;
    private import Network::*;
    private import RequirementDerivation::*;
    private import Requirements::'Segment Requirements'::'Data Center'::*;
    private import Requirements::'Segment Requirements'::Stations::*;
    private import Requirements::'Stakeholder Needs'::*;
    private import Requirements::'System Requirements'::Functions::*;
    private import Requirements::'System Requirements'::Interfaces::*;
    private import Requirements::'System Requirements'::Operations::*;
    private import Stations::*;
    doc /* The requirements as they stood when DOORS was last synchronized, and their trace. */
    package 'Stakeholder Needs' {
        requirement TW_STK_001 { doc /* The network shall provide marine weather observations for the coastal region it covers. */ attribute doorsId = "TW-STK-001"; attribute title = "Coastal coverage"; }
        requirement TW_STK_002 { doc /* Forecasters shall receive observations in time to use them in the next bulletin. */ attribute doorsId = "TW-STK-002"; attribute title = "Timely observations"; }
        requirement TW_STK_003 { doc /* Mariners shall be able to read the latest bulletin and observations from a public service. */ attribute doorsId = "TW-STK-003"; attribute title = "Public access"; }
        requirement TW_STK_004 { doc /* Field crews shall be able to service any station from a single service vessel. */ attribute doorsId = "TW-STK-004"; attribute title = "Serviceable in the field"; }
        requirement TW_STK_005 { doc /* Past observations shall be kept so earlier conditions can be reviewed. */ attribute doorsId = "TW-STK-005"; attribute title = "Observation history"; }
        requirement TW_STK_006 { doc /* Offshore stations shall keep observing without shore power. */ attribute doorsId = "TW-STK-006"; attribute title = "Off-grid operation"; }
    }
    package 'System Requirements' {
        package Functions {
            requirement TW_SYS_001 { doc /* Each station shall measure wind, air pressure and air temperature, and each buoy shall also measure waves. */ attribute doorsId = "TW-SYS-001"; attribute title = "Measure conditions"; attribute verificationMethod = "Test"; attribute risk = "Low"; }
            requirement TW_SYS_002 { doc /* Each station shall transmit its observations to the data center on a fixed schedule. */ attribute doorsId = "TW-SYS-002"; attribute title = "Scheduled transmission"; attribute verificationMethod = "Test"; attribute risk = "Low"; }
            requirement TW_SYS_003 { doc /* The data center shall ingest every observation it receives. */ attribute doorsId = "TW-SYS-003"; attribute title = "Ingest"; attribute verificationMethod = "Test"; attribute risk = "Low"; }
            requirement TW_SYS_004 { doc /* The data center shall flag observations that fail a quality check. */ attribute doorsId = "TW-SYS-004"; attribute title = "Quality control"; attribute verificationMethod = "Test"; attribute risk = "Low"; }
            requirement TW_SYS_005 { doc /* The data center shall archive every observation together with its quality flag. */ attribute doorsId = "TW-SYS-005"; attribute title = "Archive"; attribute verificationMethod = "Demonstration"; attribute risk = "Low"; }
            requirement TW_SYS_006 { doc /* The data center shall publish a marine bulletin on a fixed schedule. */ attribute doorsId = "TW-SYS-006"; attribute title = "Bulletin"; attribute verificationMethod = "Demonstration"; attribute risk = "Low"; }
            requirement TW_SYS_007 { doc /* The public service shall show the latest observation from every station. */ attribute doorsId = "TW-SYS-007"; attribute title = "Latest observations"; attribute verificationMethod = "Demonstration"; attribute risk = "Low"; }
        }
        package Interfaces {
            requirement TW_SYS_008 { doc /* Stations shall send observations to the data center over the observation interface. */ attribute doorsId = "TW-SYS-008"; attribute title = "Observation interface"; attribute verificationMethod = "Test"; attribute risk = "Low"; }
            requirement TW_SYS_009 { doc /* Stations shall report their health to the data center over the health interface. */ attribute doorsId = "TW-SYS-009"; attribute title = "Health reporting"; attribute verificationMethod = "Test"; attribute risk = "Low"; }
            requirement TW_SYS_010 { doc /* The data center shall offer observations through a documented public interface. */ attribute doorsId = "TW-SYS-010"; attribute title = "Public interface"; attribute verificationMethod = "Inspection"; attribute risk = "Low"; }
        }
        package Operations {
            requirement TW_SYS_011 { doc /* Each buoy shall run from its own solar panel and battery. */ attribute doorsId = "TW-SYS-011"; attribute title = "Own power"; attribute verificationMethod = "Analysis"; attribute risk = "Low"; }
            requirement TW_SYS_012 { doc /* Every station shall be serviceable from the service vessel. */ attribute doorsId = "TW-SYS-012"; attribute title = "Vessel access"; attribute verificationMethod = "Inspection"; attribute risk = "Low"; }
            requirement TW_SYS_013 { doc /* Each station shall keep observations it could not send and send them once the link returns. */ attribute doorsId = "TW-SYS-013"; attribute title = "Store and forward"; attribute verificationMethod = "Test"; attribute risk = "Low"; }
            requirement TW_SYS_014 { doc /* Each station shall report its operating mode. */ attribute doorsId = "TW-SYS-014"; attribute title = "Operating mode"; attribute verificationMethod = "Test"; attribute risk = "Low"; }
            requirement TW_SYS_015 { doc /* The data center shall keep a log of every bulletin it published. */ attribute doorsId = "TW-SYS-015"; attribute title = "Bulletin log"; attribute verificationMethod = "Inspection"; attribute risk = "Low"; }
        }
    }
    package 'Segment Requirements' {
        package Stations {
            requirement TW_SEG_001 { doc /* The buoy hull shall carry the sensor suite above the waterline. */ attribute doorsId = "TW-SEG-001"; attribute title = "Sensor height"; attribute verificationMethod = "Inspection"; attribute risk = "Low"; }
            requirement TW_SEG_002 { doc /* The mooring shall keep the buoy within its assigned watch circle. */ attribute doorsId = "TW-SEG-002"; attribute title = "Watch circle"; attribute verificationMethod = "Analysis"; attribute risk = "Low"; }
            requirement TW_SEG_003 { doc /* The power system shall report the battery state of charge. */ attribute doorsId = "TW-SEG-003"; attribute title = "State of charge"; attribute verificationMethod = "Test"; attribute risk = "Low"; }
            requirement TW_SEG_004 { doc /* The telemetry unit shall retry a failed transmission. */ attribute doorsId = "TW-SEG-004"; attribute title = "Retry"; attribute verificationMethod = "Test"; attribute risk = "Low"; }
            requirement TW_SEG_009 { doc /* The shore station mast shall be lowerable for maintenance. */ attribute doorsId = "TW-SEG-009"; attribute title = "Lowerable mast"; attribute verificationMethod = "Inspection"; attribute risk = "Low"; }
        }
        package 'Data Center' {
            requirement TW_SEG_005 { doc /* The ingest service shall discard duplicate observations. */ attribute doorsId = "TW-SEG-005"; attribute title = "Duplicates"; attribute verificationMethod = "Test"; attribute risk = "Low"; }
            requirement TW_SEG_006 { doc /* The quality control service shall record why an observation was flagged. */ attribute doorsId = "TW-SEG-006"; attribute title = "Flag reason"; attribute verificationMethod = "Test"; attribute risk = "Low"; }
            requirement TW_SEG_007 { doc /* The archive shall return any observation by station and time. */ attribute doorsId = "TW-SEG-007"; attribute title = "Retrieval"; attribute verificationMethod = "Demonstration"; attribute risk = "Low"; }
            requirement TW_SEG_008 { doc /* The publisher shall stamp each bulletin with its issue time. */ attribute doorsId = "TW-SEG-008"; attribute title = "Issue time"; attribute verificationMethod = "Inspection"; attribute risk = "Low"; }
        }
    }
    satisfy TW_SYS_001 by ObservingStation;
    satisfy TW_SYS_002 by ObservingStation;
    satisfy TW_SYS_003 by IngestService;
    satisfy TW_SYS_004 by QualityControl;
    satisfy TW_SYS_005 by Archive;
    satisfy TW_SYS_006 by BulletinPublisher;
    satisfy TW_SYS_007 by BulletinPublisher;
    satisfy TW_SYS_008 by ObservingStation::obsOut;
    satisfy TW_SYS_009 by ObservingStation::healthOut;
    satisfy TW_SYS_010 by DataSegment::publicOut;
    satisfy TW_SYS_011 by PowerSystem;
    satisfy TW_SYS_013 by DataLogger;
    satisfy TW_SYS_014 by ObservingStation::mode;
    satisfy TW_SYS_015 by BulletinPublisher;
    satisfy TW_SEG_001 by Hull;
    satisfy TW_SEG_002 by Mooring;
    satisfy TW_SEG_003 by Battery::stateOfCharge;
    satisfy TW_SEG_004 by TelemetryUnit;
    satisfy TW_SEG_005 by IngestService;
    satisfy TW_SEG_006 by QualityControl;
    satisfy TW_SEG_007 by Archive;
    satisfy TW_SEG_008 by BulletinPublisher;
    satisfy TW_SEG_009 by Mast;
    satisfy TW_STK_001 by ObservationNetwork;
    satisfy TW_STK_002 by ObservationNetwork;
    satisfy TW_STK_003 by ObservationNetwork;
    satisfy TW_STK_004 by ObservationNetwork;
    satisfy TW_STK_005 by ObservationNetwork;
    satisfy TW_STK_006 by ObservationNetwork;
    #derivation connection {
        end #original ::> TW_STK_001;
        end #derive ::> TW_SYS_001;
    }
    #derivation connection {
        end #original ::> TW_STK_002;
        end #derive ::> TW_SYS_002;
    }
    #derivation connection {
        end #original ::> TW_STK_002;
        end #derive ::> TW_SYS_003;
    }
    #derivation connection {
        end #original ::> TW_STK_002;
        end #derive ::> TW_SYS_004;
    }
    #derivation connection {
        end #original ::> TW_STK_005;
        end #derive ::> TW_SYS_005;
    }
    #derivation connection {
        end #original ::> TW_STK_003;
        end #derive ::> TW_SYS_006;
    }
    #derivation connection {
        end #original ::> TW_STK_003;
        end #derive ::> TW_SYS_007;
    }
    #derivation connection {
        end #original ::> TW_STK_002;
        end #derive ::> TW_SYS_008;
    }
    #derivation connection {
        end #original ::> TW_STK_004;
        end #derive ::> TW_SYS_009;
    }
    #derivation connection {
        end #original ::> TW_STK_003;
        end #derive ::> TW_SYS_010;
    }
    #derivation connection {
        end #original ::> TW_STK_006;
        end #derive ::> TW_SYS_011;
    }
    #derivation connection {
        end #original ::> TW_STK_004;
        end #derive ::> TW_SYS_012;
    }
    #derivation connection {
        end #original ::> TW_STK_002;
        end #derive ::> TW_SYS_013;
    }
    #derivation connection {
        end #original ::> TW_STK_004;
        end #derive ::> TW_SYS_014;
    }
    #derivation connection {
        end #original ::> TW_STK_005;
        end #derive ::> TW_SYS_015;
    }
    #derivation connection {
        end #original ::> TW_SYS_001;
        end #derive ::> TW_SEG_001;
    }
    #derivation connection {
        end #original ::> TW_SYS_001;
        end #derive ::> TW_SEG_002;
    }
    #derivation connection {
        end #original ::> TW_SYS_011;
        end #derive ::> TW_SEG_003;
    }
    #derivation connection {
        end #original ::> TW_SYS_013;
        end #derive ::> TW_SEG_004;
    }
    #derivation connection {
        end #original ::> TW_SYS_003;
        end #derive ::> TW_SEG_005;
    }
    #derivation connection {
        end #original ::> TW_SYS_004;
        end #derive ::> TW_SEG_006;
    }
    #derivation connection {
        end #original ::> TW_SYS_005;
        end #derive ::> TW_SEG_007;
    }
    #derivation connection {
        end #original ::> TW_SYS_006;
        end #derive ::> TW_SEG_008;
    }
    #derivation connection {
        end #original ::> TW_SYS_012;
        end #derive ::> TW_SEG_009;
    }
    dependency from ReadBulletin to TW_STK_003; // refine
    dependency from ServiceStation to TW_STK_004; // refine
    dependency from Mast to TW_SYS_012; // trace
}
