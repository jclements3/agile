# Tidewater requirements

# Specification: Stakeholder Needs

## TW-STK-001: Coastal coverage
The network shall provide marine weather observations for the coastal region it covers.
- Owner: Network Office

## TW-STK-002: Timely observations
Forecasters shall receive observations in time to use them in the next bulletin.
- Owner: Network Office

## TW-STK-003: Public access
Mariners shall be able to read the latest bulletin and observations from a public service.
- Owner: Network Office

## TW-STK-004: Serviceable in the field
Field crews shall be able to service any station from a single service vessel.
- Owner: Network Office

## TW-STK-005: Observation history
Past observations shall be kept so earlier conditions can be reviewed.
- Owner: Network Office

## TW-STK-006: Off-grid operation
Offshore stations shall keep observing without shore power.
- Owner: Network Office

# Specification: System Requirements

## 14: Functions

### TW-SYS-001: Measure conditions
Each station shall measure wind, air pressure and air temperature, and each buoy shall also measure waves.
- Verification Method: Test
- Owner: Station Engineering
- derived from -> TW-STK-001

### TW-SYS-002: Scheduled transmission
Each station shall transmit its observations to the data center on a fixed schedule.
- Verification Method: Test
- Owner: Station Engineering
- derived from -> TW-STK-002

### TW-SYS-003: Ingest
The data center shall ingest every observation it receives.
- Verification Method: Test
- Owner: Data Services
- derived from -> TW-STK-002

### TW-SYS-004: Quality control
The data center shall flag observations that fail a quality check.
- Verification Method: Test
- Owner: Data Services
- derived from -> TW-STK-002

### TW-SYS-005: Archive
The data center shall archive every observation together with its quality flag.
- Verification Method: Demonstration
- Owner: Data Services
- derived from -> TW-STK-005

### TW-SYS-006: Bulletin
The data center shall publish a marine bulletin twice a day, on a fixed schedule.
- Verification Method: Demonstration
- Owner: Data Services
- derived from -> TW-STK-003

### TW-SYS-007: Latest observations
The public service shall show the latest observation from every station.
- Verification Method: Demonstration
- Owner: Data Services
- derived from -> TW-STK-003

## 18: Interfaces

### TW-SYS-008: Observation interface
Stations shall send observations to the data center over the observation interface.
- Verification Method: Test
- Owner: Station Engineering
- derived from -> TW-STK-002

### TW-SYS-009: Health reporting
Stations shall report their health to the data center over the health interface.
- Verification Method: Test
- Owner: Station Engineering
- derived from -> TW-STK-004

### TW-SYS-010: Public interface
The data center shall offer observations through a documented public interface.
- Verification Method: Inspection
- Owner: Data Services
- derived from -> TW-STK-003

## 25: Operations

### TW-SYS-011: Own power
Each buoy shall run from its own solar panel and battery.
- Verification Method: Analysis
- Owner: Station Engineering
- derived from -> TW-STK-006

### TW-SYS-012: Vessel access
Every station shall be serviceable from the service vessel.
- Verification Method: Inspection
- Owner: Field Operations
- derived from -> TW-STK-004

### TW-SYS-013: Store and forward
Each station shall keep observations it could not send and send them once the link returns.
- Verification Method: Test
- Owner: Station Engineering
- derived from -> TW-STK-002

### TW-SYS-014: Operating mode
Each station shall report its operating mode.
- Verification Method: Test
- Owner: Station Engineering
- derived from -> TW-STK-004

### TW-SYS-015: Bulletin log
The data center shall keep a log of every bulletin it published.
- Verification Method: Inspection
- Owner: Data Services
- derived from -> TW-STK-005

### TW-SYS-016: Common time
All stations and the data center shall use a common time reference.
- Verification Method: Test
- Owner: Station Engineering
- derived from -> TW-STK-002

# Specification: Segment Requirements

## 30: Stations

### TW-SEG-001: Sensor height
The buoy hull shall carry the sensor suite above the waterline.
- Verification Method: Inspection
- Owner: Station Engineering
- derived from -> TW-SYS-001

### TW-SEG-002: Watch circle
The mooring shall keep the buoy within its assigned watch circle.
- Verification Method: Analysis
- Owner: Station Engineering
- derived from -> TW-SYS-001

### TW-SEG-003: State of charge
The power system shall report the battery state of charge.
- Verification Method: Test
- Owner: Station Engineering
- derived from -> TW-SYS-011

### TW-SEG-004: Retry
The telemetry unit shall retry a failed transmission.
- Verification Method: Test
- Owner: Station Engineering
- derived from -> TW-SYS-013

## 35: Data Center

### TW-SEG-005: Duplicates
The ingest service shall discard duplicate observations.
- Verification Method: Test
- Owner: Data Services
- derived from -> TW-SYS-003

### TW-SEG-006: Flag reason
The quality control service shall record why an observation was flagged.
- Verification Method: Test
- Owner: Data Services
- derived from -> TW-SYS-004

### TW-SEG-007: Retrieval
The archive shall return any observation by station and time.
- Verification Method: Demonstration
- Owner: Data Services
- derived from -> TW-SYS-005

### TW-SEG-008: Issue time
The publisher shall stamp each bulletin with its issue time.
- Verification Method: Inspection
- Owner: Data Services
- derived from -> TW-SYS-006
