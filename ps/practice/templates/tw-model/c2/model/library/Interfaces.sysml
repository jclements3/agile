// generated by xmi2sysml.pl from tidewater.xmi -- review before committing; TODO lines need a person
package Interfaces {
    private import Types::*;
    doc
        /*
         * What crosses each segment boundary: interface blocks with flow properties, and the signals they carry.
         */
    item def ObservationRecord {
        doc /* One timed set of measurements from one station. */
        attribute stationId : ScalarValues::String;
        attribute observedAt : ScalarValues::String;
        attribute qualityFlag : ScalarValues::Integer;
    }
    item def HealthReport {
        doc /* Battery, mode and fault state of one station. */
        attribute stationId : ScalarValues::String;
        attribute stateOfCharge : ScalarValues::Real;
    }
    item def Bulletin {
        doc /* The published marine bulletin. */
        attribute issuedAt : ScalarValues::String;
    }
    port def ObservationIF {
        doc /* Observations from a station to the data center. */
        out item observation : ObservationRecord;
    }
    port def HealthIF {
        doc /* Health reports from a station to the data center. */
        out item health : HealthReport;
    }
    port def PublicIF {
        doc /* Bulletins and latest observations to the public. */
        out item bulletin : Bulletin;
        out item latest : ObservationRecord;
    }
    port def PowerIF {
        doc /* DC power between the power system and its loads. */
        out attribute supply : Power;
    }
}
