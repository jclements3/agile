// generated by xmi2sysml.pl from tidewater.xmi -- review before committing; TODO lines need a person
package Stations {
    private import Analysis::*;
    private import DataCenter::*;
    private import Interfaces::*;
    private import Requirements::'System Requirements'::Functions::*;
    private import Requirements::'System Requirements'::Interfaces::*;
    private import Requirements::'System Requirements'::Operations::*;
    private import Types::*;
    doc /* Everything that goes out to a site: moored buoys and shore stations. */
    part def StationSegment {
        // TODO stereotype Tidewater_Profile:L2Segment on this element (xmi:id _22_1_7f3a0c1_a16b5d7b3d55) not converted
        doc /* All the observing stations of the network. */
        part buoys : MooredBuoy[1..*];
        part shoreStations : ShoreStation[1..*];
        port obsOut : ObservationIF;
        port healthOut : HealthIF;
        connection connect obsOut to buoys.obsOut;
        connection connect obsOut to shoreStations.obsOut;
    }
    part def ObservingStation {
        // TODO stereotype Tidewater_Profile:L3Station on this element (xmi:id _22_1_7f3a0c1_b0496aff7797) not converted
        doc /* What every station has: sensors, a logger, telemetry and the two outgoing ports. */
        part sensors : SensorSuite;
        part logger : DataLogger;
        part telemetry : TelemetryUnit;
        attribute stationId : ScalarValues::String;
        port obsOut : ObservationIF;
        port healthOut : HealthIF;
        port mode { out attribute flowValue : StationMode; }
        connection toLogger connect sensors.dataOut to logger.dataIn;
        connection toTelemetry connect logger.uplink to telemetry.dataIn;
        connection connect telemetry.obsOut to obsOut;
    }
    part def MooredBuoy :> ObservingStation {
        // TODO stereotype Tidewater_Profile:L3Station on this element (xmi:id _22_1_7f3a0c1_f0c0798ba6a3) not converted
        doc /* An offshore station on a mooring, powered by its own solar panel. */
        part hull : Hull;
        part mooring : Mooring;
        part power : PowerSystem;
        part waveSensor : WaveSensor;
        // TODO uml:StateMachine 'BuoyModes' (xmi:id _22_1_7f3a0c1_7a13eb20b93a): no SysML v2 mapping in this converter
    }
    part def ShoreStation :> ObservingStation {
        // TODO stereotype Tidewater_Profile:L3Station on this element (xmi:id _22_1_7f3a0c1_cc7643f6cda1) not converted
        doc /* A station on a mast at the shore, on mains power. */
        part mast : Mast;
    }
    part def PowerSystem {
        // TODO stereotype Tidewater_Profile:L4Subsystem on this element (xmi:id _22_1_7f3a0c1_8ec6b88fc131) not converted
        doc /* Solar generation, storage and regulation for a buoy. */
        doc
            /*
             * Per SSDD section 4.3 the power budget is TBD pending the 2024 trade study. Do not change without CCB approval.
             */
        part solar : SolarPanel;
        part battery : Battery;
        part regulator : ChargeRegulator;
        attribute averageLoad : Power;
        port supplyOut : PowerIF;
        connection charge connect solar.'out' to regulator.'in';
        connection store connect regulator.toBattery to battery.terminal;
        part balance : EnergyBalance;
        bind balance.generation = solar.ratedPower;
        bind balance.storage = battery.capacity;
        bind balance.load = averageLoad;
    }
    part def SensorSuite {
        // TODO stereotype Tidewater_Profile:L4Subsystem on this element (xmi:id _22_1_7f3a0c1_7318f3d7efae) not converted
        doc /* The meteorological sensors common to every station. */
        part anemometer : Anemometer;
        part barometer : Barometer;
        part thermometer : Thermometer;
        port dataOut { out attribute flowValue : ScalarValues::String; }
    }
    part def DataLogger {
        // TODO stereotype Tidewater_Profile:L4Subsystem on this element (xmi:id _22_1_7f3a0c1_975eb7368c70) not converted
        // TODO stereotype Tidewater_Profile:Procured on this element (xmi:id _22_1_7f3a0c1_813b4bf805b8) not converted
        doc /* Timestamps and stores observations until they are sent. */
        doc
            /*
             * Per SRS rev C para 3.2.1 the logger shall buffer observations while the link is down (see ICD-004 Table 7, TBR). Copied from the SRS 2023-11 baseline.
             */
        attribute bufferedRecords : ScalarValues::Integer;
        port dataIn { in attribute flowValue : ScalarValues::String; }
        port uplink : ObservationIF;
    }
    part def TelemetryUnit {
        // TODO stereotype Tidewater_Profile:L4Subsystem on this element (xmi:id _22_1_7f3a0c1_605f0a973764) not converted
        doc /* Sends observations and health over the cellular or satellite link. */
        part modem : Modem;
        part antenna : Antenna;
        port dataIn : ~ObservationIF;
        port obsOut : ObservationIF;
    }
    part def Hull {
        // TODO stereotype Tidewater_Profile:L4Subsystem on this element (xmi:id _22_1_7f3a0c1_22a27dbde52b) not converted
        doc /* The floating body that carries everything else. */
        part mastFrame : SensorMast;
        part ballast : Ballast;
    }
    part def Mooring {
        // TODO stereotype Tidewater_Profile:L4Subsystem on this element (xmi:id _22_1_7f3a0c1_3697adba15fb) not converted
        doc /* Holds the buoy on station. */
        part chain : MooringChain;
        part anchor : Anchor;
    }
    part def Mast {
        // TODO stereotype Tidewater_Profile:L4Subsystem on this element (xmi:id _22_1_7f3a0c1_02f2df7ec70b) not converted
        doc /* Holds the shore sensors at height. */
    }
    part def SolarPanel {
        // TODO stereotype Tidewater_Profile:L5Assembly on this element (xmi:id _22_1_7f3a0c1_0efc9f0503d9) not converted
        // TODO stereotype Tidewater_Profile:Procured on this element (xmi:id _22_1_7f3a0c1_6f592009da70) not converted
        doc /* Generates power. */
        attribute ratedPower : Power = 40;
        port 'out' : PowerIF;
    }
    part def Battery {
        // TODO stereotype Tidewater_Profile:L5Assembly on this element (xmi:id _22_1_7f3a0c1_37e0ed9f5054) not converted
        doc /* Stores power for night and cloud. */
        part cells : Cell[4];
        attribute capacity : Energy = 400;
        attribute stateOfCharge : Percentage;
        port terminal : ~PowerIF;
    }
    part def ChargeRegulator {
        // TODO stereotype Tidewater_Profile:L5Assembly on this element (xmi:id _22_1_7f3a0c1_57ee0e9db9ef) not converted
        doc /* Keeps the battery within its charge limits. */
        port 'in' : ~PowerIF;
        port toBattery : PowerIF;
    }
    part def Anemometer {
        // TODO stereotype Tidewater_Profile:L5Assembly on this element (xmi:id _22_1_7f3a0c1_5c46304f8090) not converted
        doc /* Wind speed and direction. */
    }
    part def Barometer {
        // TODO stereotype Tidewater_Profile:L5Assembly on this element (xmi:id _22_1_7f3a0c1_f4b98fde9526) not converted
        doc /* Air pressure. */
    }
    part def Thermometer {
        // TODO stereotype Tidewater_Profile:L5Assembly on this element (xmi:id _22_1_7f3a0c1_3540e65af372) not converted
        doc /* Air temperature. */
    }
    part def WaveSensor {
        // TODO stereotype Tidewater_Profile:L5Assembly on this element (xmi:id _22_1_7f3a0c1_914da2983651) not converted
        doc /* Wave height and period, from motion. */
    }
    part def Modem {
        // TODO stereotype Tidewater_Profile:L5Assembly on this element (xmi:id _22_1_7f3a0c1_d49e3c2b0910) not converted
        // TODO stereotype Tidewater_Profile:Procured on this element (xmi:id _22_1_7f3a0c1_79c944e3d0f4) not converted
        doc /* The radio link. */
    }
    part def Antenna {
        // TODO stereotype Tidewater_Profile:L5Assembly on this element (xmi:id _22_1_7f3a0c1_5d05ba27382c) not converted
        doc /* The radio antenna. */
    }
    part def SensorMast {
        // TODO stereotype Tidewater_Profile:L5Assembly on this element (xmi:id _22_1_7f3a0c1_f247222c1bde) not converted
        doc /* The frame on the hull that carries the sensors. */
    }
    part def Ballast {
        // TODO stereotype Tidewater_Profile:L5Assembly on this element (xmi:id _22_1_7f3a0c1_617a21e72f60) not converted
        doc /* Keeps the hull upright. */
    }
    part def MooringChain {
        // TODO stereotype Tidewater_Profile:L5Assembly on this element (xmi:id _22_1_7f3a0c1_f6eaa9b17d90) not converted
        doc /* Chain between hull and anchor. */
    }
    part def Anchor {
        // TODO stereotype Tidewater_Profile:L5Assembly on this element (xmi:id _22_1_7f3a0c1_bf1b75300cdf) not converted
        doc /* Holds the mooring to the seabed. */
    }
    part def Cell {
        // TODO stereotype Tidewater_Profile:L6Component on this element (xmi:id _22_1_7f3a0c1_1d3585f6f7ce) not converted
        doc /* One battery cell. */
    }
    dependency from ObservingStation to TW_SYS_001; // trace
    dependency from ObservingStation to TW_SYS_002; // trace
    dependency from ObservingStation to TW_SYS_003; // trace
    dependency from ObservingStation to TW_SYS_004; // trace
    dependency from ObservingStation to TW_SYS_005; // trace
    dependency from ObservingStation to TW_SYS_006; // trace
    dependency from ObservingStation to TW_SYS_007; // trace
    dependency from ObservingStation to TW_SYS_008; // trace
    dependency from ObservingStation to TW_SYS_009; // trace
    dependency from ObservingStation to TW_SYS_010; // trace
    dependency from ObservingStation to TW_SYS_011; // trace
    dependency from DataLogger to IngestService; // trace
}
