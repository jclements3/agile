// generated by xmi2sysml.pl from tidewater.xmi -- review before committing; TODO lines need a person
package Types {
    doc /* Value types and units used across the network. */
    attribute def Power :> ScalarValues::Real {
        // SysML 1.x unit: watt -- specialize an ISQ quantity value by hand
    }
    attribute def Energy :> ScalarValues::Real {
        // SysML 1.x unit: watt hour -- specialize an ISQ quantity value by hand
    }
    attribute def Percentage :> ScalarValues::Real {
        // SysML 1.x unit: percent -- specialize an ISQ quantity value by hand
    }
    // TODO uml:InstanceSpecification 'watt' (xmi:id _22_1_7f3a0c1_635c3454811f): no SysML v2 mapping in this converter
    // TODO uml:InstanceSpecification 'watt hour' (xmi:id _22_1_7f3a0c1_6f4c2f1b2938): no SysML v2 mapping in this converter
    // TODO uml:InstanceSpecification 'percent' (xmi:id _22_1_7f3a0c1_57eac3b61581): no SysML v2 mapping in this converter
    enum def StationMode {
        enum observing;
        enum degraded;
        enum maintenance;
        enum recovered;
    }
}
