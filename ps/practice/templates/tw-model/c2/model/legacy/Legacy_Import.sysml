// generated by xmi2sysml.pl from tidewater.xmi -- review before committing; TODO lines need a person
package 'Legacy Import' {
    private import Interfaces::*;
    private import Stations::*;
    private import Types::*;
    doc /* Imported from the SRS and SSDD in 2023. Clean up later. */
    part def Battery_old {
        doc /* Copy of Battery from the 2023 SRS import. Use Battery. */
        part cells : Cell[4];
        attribute capacity : Energy = 400;
        attribute stateOfCharge : Percentage;
        port terminal : ~PowerIF;
    }
    part def 'Copy of SensorSuite' {
        doc /* The meteorological sensors common to every station. */
        part anemometer : Anemometer;
        part barometer : Barometer;
        part thermometer : Thermometer;
        port dataOut { out attribute flowValue : ScalarValues::String; }
    }
    part def 'TBD Component' {
        doc /* Placeholder from the document import. TBD. */
    }
    part def 'Requirement from slide 14' {
        doc /* The system shall be available 99.5% of the time (2024-03 program review, slide 14). */
    }
}
