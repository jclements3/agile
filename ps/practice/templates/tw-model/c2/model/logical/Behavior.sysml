// generated by xmi2sysml.pl from tidewater.xmi -- review before committing; TODO lines need a person
package Behavior {
    private import Interfaces::*;
    doc /* The observation cycle, from sampling to the published bulletin. */
    action def ObserveCoast {
        doc /* One cycle of the network: sample, send, ingest, check, archive, publish. */
        out bulletin : Bulletin;
        action sample : SampleSensors;
        action 'send' : TransmitObservations;
        action ingest : IngestObservations;
        action check : CheckQuality;
        action store : ArchiveObservations;
        action publish : PublishBulletin;
        // TODO uml:ForkNode 'after check' (xmi:id _22_1_7f3a0c1_56146662ad81): activity node not converted
        action 'log health';
        // TODO uml:InputPin 'report' (xmi:id _22_1_7f3a0c1_c91b3000bf85): pin (object flow) not converted
        first start then sample;
        first sample then 'send';
        first 'send' then ingest;
        first ingest then check;
        first check then store;
        first store then publish;
        first publish then done;
        // TODO uml:ObjectFlow (xmi:id _22_1_7f3a0c1_49fcb94547f1): activity edge not converted (object flow, or an end that is a decision/fork/pin)
        // TODO uml:ControlFlow (xmi:id _22_1_7f3a0c1_b1c9f188a001): activity edge not converted (object flow, or an end that is a decision/fork/pin)
    }
    action def SampleSensors {
        doc /* Read every sensor and timestamp the readings. */
        out record : ObservationRecord;
    }
    action def TransmitObservations {
        doc /* Send the buffered records; keep them if the link is down. */
        in record : ObservationRecord;
    }
    action def IngestObservations {
        doc /* Receive records and discard duplicates. */
        inout record : ObservationRecord;
    }
    action def CheckQuality {
        doc /* Range, step and consistency checks; set the flag and the reason. */
        inout record : ObservationRecord;
    }
    action def ArchiveObservations {
        doc /* Store each record with its flag. */
        in record : ObservationRecord;
    }
    action def PublishBulletin {
        doc /* Write the bulletin from the latest good observations and publish it. */
        out bulletin : Bulletin;
    }
    action def ReportHealth {
        doc /* Send battery state, mode and faults. */
        out report : HealthReport;
    }
}
